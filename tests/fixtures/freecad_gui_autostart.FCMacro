"""Exercise workbench GUI auto-start in a disposable FreeCAD process."""

import importlib
import importlib.util
import json
import os
import sys
from pathlib import Path

from PySide import QtCore

root = Path(os.environ["MCP_TEST_REPO"]) / "freecad" / "RobustMCPBridge"
sys.path.insert(0, str(root.parents[1]))
params = FreeCAD.ParamGet("User parameter:BaseApp/Preferences/Mod/RobustMCPBridge")  # noqa: F821
params.SetBool("AutoStart", True)
params.SetBool("AutoStartHeadless", False)
params.SetInt("XMLRPCPort", int(os.environ["MCP_TEST_XMLRPC_PORT"]))
params.SetInt("SocketPort", int(os.environ["MCP_TEST_SOCKET_PORT"]))
package_name = "freecad.MCPActualProbe"


def load_workbench():
    """Load this checkout as a FreeCAD namespace workbench."""
    spec = importlib.util.spec_from_file_location(
        package_name, root / "__init__.py", submodule_search_locations=[str(root)]
    )
    if spec is None or spec.loader is None:
        raise RuntimeError("Unable to load workbench test package")
    module = importlib.util.module_from_spec(spec)
    sys.modules[package_name] = module
    spec.loader.exec_module(module)


def begin():
    """Run the production initializer after the GUI event loop is ready."""
    os.environ.pop("FREECAD_MCP_TESTING", None)
    load_workbench()


def finish():
    """Record the bridge state, stop it, and close the empty GUI."""
    try:
        commands = importlib.import_module(package_name + ".commands")

        plugin = commands._mcp_plugin
        started = plugin is not None and plugin.is_running and not plugin._headless
        listening = bool(
            started
            and plugin._xmlrpc_server is not None
            and plugin._socket_server is not None
        )
        Path(os.environ["MCP_TEST_RESULT"]).write_text(
            json.dumps({"started": started, "listening": listening}), encoding="utf-8"
        )
        if plugin is not None:
            plugin.stop()
    finally:
        FreeCADGui.getMainWindow().close()  # noqa: F821 - injected by FreeCAD


QtCore.QTimer.singleShot(1000, begin)
QtCore.QTimer.singleShot(6500, finish)
